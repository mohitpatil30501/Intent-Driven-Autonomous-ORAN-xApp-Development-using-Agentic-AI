module o-ran-cti-tn-pon {
  yang-version 1.1;
  namespace "urn:o-ran:cti-tn-pon:1.0";
  prefix "or-cti-pon";


  import o-ran-cti-common {
    prefix or-ctic;
  }

  import o-ran-cti-tn-generic {
    prefix or-ctig;
  }
  
  import o-ran-common-identity-refs {
	prefix or-refs;
  }

  import ietf-interfaces {
    prefix if;
  }

  import ietf-yang-types {
    prefix yang;
  }

  import ietf-inet-types {
    prefix inet;
  }

  import bbf-xpon-if-type {
    prefix bbf-xponift;
  }

  import bbf-if-type {
    prefix bbfift;
  }

  import bbf-xpongemtcont {
    prefix bbf-xpongemtcont;
  }

  organization "O-RAN Alliance";

  contact
    "www.o-ran.org";

  description
    "This module defines the configuration of for the CTI transport node that for
    PON defined transport nodes that implement the O-RAN WG4 Cooperative transport Interface.

    Copyright 2020 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2022-06-28" {
    description
      "version 3.0.0
      1) non-backward compatible changes to switch to camelCase";

    reference "ORAN-WG4.CTI-TCP.0-v03.00";
  }

  identity ponTransport {
    base "or-refs:o-ran-transport-technology-base";
    description
      "an identity corresponding to PON transport";
  }

  grouping ponSessionConfigDataGrp {
    description
      "A grouping of PON specific info reflecting the ingress point in the PON system the O-RU (interface) corresponding to a given CTI session ID: OLT Channel Termination, ONU, ONU UNI";

    leaf oltChannelTerminationRef {
      type if:interface-ref;
      must "derived-from-or-self(/if:interfaces"
         + "/if:interface[if:name=current()]/if:type,"
         + "'bbf-xponift:channel-termination')" 
      {
        error-message
          "Must reference a channel termination.";
      }
      description "Reference to a PON OLT Channel Termination";
	}

    leaf ctiSessionIdIngress {
      type if:interface-ref;
      must "derived-from-or-self(/if:interfaces"
         + "/if:interface[if:name=current()]/if:type,"
         + "'bbf-xponift:olt-v-enet') or
           derived-from-or-self(/if:interfaces"
         + "/if:interface[if:name=current()]/if:type,"
         + "'bbf-xponift:olt-v-ani')"
      {
        error-message
          "Must either reference an OLT vENET interface which is the
           local representation in the OLT of an ONU UNI
           interface, or reference an OLT vANI interface wich is the
           local representation in the OLT of an ONU";
      }
      description "Reference to an ONU or ONU UNI.";
    }
  }

  grouping ponFlowConfigDataGrp {
    description
      "A T-CONT being used for carrying upstream traffic pertaining to a CTI Session ID + Flow ID";

    leaf associatedTcont {
      type leafref {
        path '/bbf-xpongemtcont:xpongemtcont/bbf-xpongemtcont:'
           + 'tconts/bbf-xpongemtcont:tcont/bbf-xpongemtcont:'
           + 'name';
      }
      description
        "Reference to a T-CONT.";
    }

  }

  grouping ponRangingInfoGrp {
    description "a grouping for PON ranging info";

    leaf ponUseNotifications {
      type boolean;
      mandatory true;
      description "whether PON notifications are used to this CTI client";
    }
    leaf ponMinNotificationTa {
      when "../ponUseNotifications ='true'";
      type uint16;
      units milliseconds;
      description "the minimum notification timing advance";
    }
  }

  grouping ponFlowInfoGrp {
    description "a grouping for the PON specific flow information";
    choice filterType {
      description "the filter type for this flow";
      case ethernet {
        container l2Flow {
          must "(sourceMac)or(destinationMac)or(ethertype)or(pcp)or(vlanId)";
          description "field(s) for L2 filter";
          uses or-ctic:layer2FilterGrp;
        }
      }
      case udpip {
        container udpipFlow {
          must "(sourceAddress)or(sourcePrefix)or(destinationAddress)or(destinationPrefix)or(dscp)or((sourcePortStart)and(sourcePortEnd))";
          description "field(s) for UDP/IP filter";
          uses or-ctic:layer3and4FilterGrp;
        }
      }
    }
  }

  grouping ponCtiEgressIfGrp {
      description "Configuration of the egress interface on OLT for CTI towards CTI client in O-DU";

      leaf ctiL2Interface {
      type if:interface-ref;
      must "derived-from-or-self(/if:interfaces"
         + "/if:interface[if:name=current()]/if:type,"
         + "'bbfift:vlan-sub-interface') or "
         + "derived-from-or-self(/if:interfaces"
         + "/if:interface[if:name=current()]/if:type,"
         + "'bbfift:l2-termination')"  {
                error-message
            "Must reference a vlan-sub-interface or a
            l2-termination interface.";
         }
      description "Reference to a L2 interface.";
      }
      leaf ctiUseOfIp {
        type boolean;
        description "Use IP transport capabilities (RFC 8344) of the L2 interface (if available) for CTI.";
      }
  }

  augment "/or-ctig:ctiTn/or-ctig:ctiSession/or-ctig:technologySpecificSessionInfo" {
    when "(derived-from-or-self(../../transportType," + "'ponTransport'))";
	description "augmentation for session data";
    uses ponSessionConfigDataGrp;
  }

  augment "/or-ctig:ctiTn/or-ctig:ctiSession/or-ctig:ctiFlows/or-ctig:technologySpecificFlowInfo" {
    when "(derived-from-or-self(../../../transportType," + "'ponTransport'))";
    description "augmentation for flow configuration data";
    uses ponFlowConfigDataGrp;
  }

  augment "/or-ctig:ctiTn/or-ctig:ctiSession/or-ctig:ctiFlows/or-ctig:technologySpecificFlowInfo" {
    when "(derived-from-or-self(../../../transportType," + "'ponTransport'))";
    description "augmentation for flow configuration data";
    uses ponFlowInfoGrp;
  }

  augment "/or-ctig:ctiTn/or-ctig:ctiTnServer/or-ctig:serverClientPair" {
    when "(derived-from-or-self(../../transportType," + "'ponTransport'))";
    description "augmentation for CTI interface";
    uses ponCtiEgressIfGrp;
  }

  augment "/or-ctig:ctiTn/or-ctig:ctiClient/or-ctig:technologySpecificClientInfo" {
    when "(derived-from-or-self(../../transportType," + "'ponTransport'))";
    description "augmentation for PON ranging info";
    uses ponRangingInfoGrp;
  }

}
