module o-ran-cti-tn-generic {
  yang-version 1.1;
  namespace "urn:o-ran:cti-tn-generic:2.0";
  prefix "or-cti-tn";

  import o-ran-cti-common {
    prefix or-ctic;
  }

  import ietf-yang-types {
    prefix yang;
  }

  import ietf-inet-types {
    prefix inet;
  }

  import o-ran-common-identity-refs {
    prefix or-refs;
  }

  organization "O-RAN Alliance";

  contact
    "www.o-ran.org";

  description
    "This module defines the configuration of for a generic CTI transport node
    that implements the O-RAN WG4 Cooperative transport Interface. It is intended
    that transport technology specific augmentations will be used to completely define
    the configuration of a fully functional CTI Transport Node.

    Copyright 2022 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2022-04-15" {
      description
        "version 3.0.0

        1) non-backward compatible changes to switch to camelCase";

      reference "ORAN-WG4.CTI-TMP.0-v03.00";
    }
  revision "2020-10-26" {
    description
      "version 1.0.0

      1) initial version";

    reference "ORAN-WG4.CTI-TMP.0-v01.00";
  }

  grouping tnCtiCharacteristics {
    description "a grouping for tn characteristics";

    leaf tnCtiMessageTimingPerformance {
      type uint8;
      units 20-microseconds;
      config false;
      mandatory true;
      description
        "The minimal spacing needed between the arrival time of the CTI message
        and the start boundary at Ra of the mobile slot N being reported in the message";
    }
    leaf ctiReportRateCategory {
      type uint8 {
        range "1..5";
      }
      config false;
      mandatory true;
      description "the supported message interval, where 1 = 5ms, 2 = 2ms, 3 = 1 ms
      4 = 0.5ms, 5 = 0.25 ms";
      reference "O-RAN.WG4.CTI-TCP: Table CTI Message Rate Categories for O-DU or TN";
    }
	  leaf-list supportedVersions {
		  type or-ctic:ctiVersion;
      config false;
      min-elements 1;
      description "the list of versions of CTI TC-Plane that are supported by the CTI client";
    }
  }

  grouping clientListGrp {
    description "a grouping of a CTI client list";

    list ctiClient {
      key name;
      description "a list of CTI clients";

      leaf name {
        type string;
        description "the unique name of a CTI client";
      }
      leaf ctiEnable {
        type boolean;
        mandatory true;
        description "whether the client is enabled for CTI";
      }
      leaf-list version {
        type or-ctic:ctiVersion;
        min-elements 1;
        description "the list of version of CTI TC-Plane that can be used with the client";
      }

      choice connectivityType {
        description "the connectivity type";
        case ethernet {
          leaf ctiClientMacAddr {
            type yang:mac-address;
            description "the destination address used for CTI messages to the server";
          }
	      }
	      case udpip {
          leaf ctiClientHost {
            type inet:host;
            description "host (remote IP address or FQDN) for the CTI client";
          }
		    }
	    }

      container technologySpecificClientInfo {
        description
          "a container to be augmented by technology specific models that is used to configure
          technology specific parameters for interaction with this client";
      }
      list patterns {
        key patternId;
        min-elements 1;
        description "a list of patterns";

        uses or-ctic:ctiPatternGrp;
      }
    }
  }

  grouping ctiFlowsInUseGrp {
    description "the cti flow in use group";
    list ctiFlows {
      key ctiFlowId;
      description "a list of CTI flows";

      leaf ctiFlowId {
        type uint8;
        description "a CTI flow-id";
      }
      leaf maxPortionT34Latency {
        type uint16;
        units 5-microseconds;
        description
          "The portion of the maximum T34 latency allocated to TN-TU segment - used to optimize the operation of the TN node";
      }
      container technologySpecificFlowInfo {
        description
          "a container to be augmented by technology specific models that is used to configure
          the technology specific transport parameters associated with the cti-flow-ID in the context of the given cti-session-id";
      }
    }
  }

  grouping ctiSessionIdGrp {
    description "the cti-session-id group";
    list ctiSession {
      key id;
      description "a CTI session";

      leaf id {
        type string;
        description "the identity of a cti session";
      }
      leaf ctiClient {
        type leafref {
          path "/ctiTn/ctiClient/name";
        }
        mandatory true;
        description "";
      }

     leaf ctiTnServer {
        type leafref {
          path "/ctiTn/ctiTnServer/name";
        }
        mandatory true;
        description "";
      }

      leaf ctiNominalReportMsgInterval {
        type uint8;
        units 0.25-milliseconds;
        mandatory true;
        description "the nominal CTI reporting messsage interval";
      }

      uses ctiFlowsInUseGrp;

	    container technologySpecificSessionInfo {
        description
          "a container to augmented by technology specific models";
      }
    }
  }

  grouping ctiTnServerGrp {
    description "the cti tn server grouping";
    list ctiTnServer {
      key name;
      description "list of cti tn servers";

      leaf name {
        type string;
        description "a unique name/identity for a cti-tn-server";
      }
      leaf ctiEnable {
        type boolean;
        default false;
        description "whether the cti server is enabled";
      }
      leaf-list ctiSessionIds {
        type leafref {
          path "/ctiTn/ctiSession/id";
        }
        config false;
        description "read-only list of CTI session IDs handled by this CTI server";
      }

	    list serverClientPair {
        key clientName;
        description "a list of a CTI clients in contact with this CTI server, to be augmented by technology-specific connectivity parameters";

		    leaf clientName {
			    type leafref {
			      path "/ctiTn/ctiClient/name";
			    }
			    description "the name of the CTI client";
		    }
	    }
	  }
  }

  container ctiTn {
    description
      "the top level container for CTI TN generic, i.e., transport
      technology agnostic, configuration and operational data";

    leaf transportType {
      type identityref {
        base or-refs:o-ran-transport-technology-base;
      }
      description "a identity ref used in conditional augmentation";
    }
    container ctiTransport {
      presence "Enable CTI Transport";
      description
        "container for transport parameters";
      uses or-ctic:subtypeGrp;
      uses or-ctic:ctiListeningUdpPortGrp;
    }
    container ctiTimers {
      presence "Enable CTI Timers";
      description
        "container for mandatory CTI Timers";
      uses or-ctic:ctiTimersGrp;
    }
    uses tnCtiCharacteristics;
    uses clientListGrp;
    uses ctiTnServerGrp;
    uses ctiSessionIdGrp;
  }

}
